module Test {
     yang-version 1;
     namespace "http://huawei.com";
     prefix Ant;
     description "Interval before a route is declared invalid";

     container interface1 {
          leaf ifType {
                type string;
          }
     }

    typedef type1 {
        type int8;
    }


    typedef type2 {
        type string {
        length "1..253";
        pattern
          '(([0-9]|[1-9][0-9]|1[0-9][0-9]|2[0-4][0-9]|25[0-5])\.){3}([0-9]|[1-9][0-9]|1[0-9][0-9]|2[0-4][0-9]|25[0-5])/(([0-9])|([1-2][0-9])|(3[0-2]))';
      }
}


    typedef type3 {
        type int16;
    }

    typedef type4 {
        type int32;
    }
    typedef type5 {
        type int64;
    }

    typedef type6 {
        type uint8;
    }

    typedef type7 {
        type uint16;
    }

    typedef type8 {
        type uint32;
    }

    typedef type9 {
        type uint64;
    }

    typedef type10 {
        type type1;
    }

    typedef type11 {
        type int8;
    }

    typedef type12 {
        type type1;
    }

    /* need to impelement
    typedef type13 { 
        type decimal64;
    }
    
    typedef type14 { 
        type binary;
    }
    */

    /*
    typedef type15 { 
        type bits {
             bit disable-nagle {
                 position 0;
             }
             bit auto-sense-speed {
                 position 1;
             }
             bit 10-Mb-only {
                 position 2;
             }
         }
    }
   */ 

/*
    typedef type16 { 
        type instance-identifier;
    }

    typedef type17 { 
        type leafref;
    }
 
    typedef type18 { 
        type identityref;
    }
*/

    typedef type19 { 
        type string;
    }


augment "/Test/interface1" {

      when "ifType='ds0'";
           reference
      "RFC 2578: Structure of Management Information Version 2 (SMIv2)";
      status current;

leaf-list foo {
    type string;
}

      list port_list {
  key "port";
          leaf port {
               type int16;
         }
       }

container abc {

    leaf typedef1 {
       type type1;
     }

    leaf typedef2 {
       type type2;
     }

    leaf typedef3 {
       type type3;
     }

    leaf typedef4 {
       type type4;
     }
    leaf typedef5 {
       type type5;
     }

    leaf typedef6 {
       type type6;
     }
    leaf typedef7 {
       type type8;
     }

    leaf typedef9 {
       type type9;
     }
    leaf typedef10 {
       type type10;
     }

    leaf typedef11 {
       type type11;
     }
    leaf typedef12 {
       type type12;
     }
}
    }
}
